--
-- LCTX-NET-CTRL-DEV.mib
-- MIB generated by MG-SOFT Visual MIB Builder Version 6.0  Build 88
-- Friday, February 17, 2017 at 18:16:20
--

	LCTX-NET-CTRL-DEV DEFINITIONS ::= BEGIN
 
		IMPORTS
			enterprises, Integer32, OBJECT-TYPE, MODULE-IDENTITY			
				FROM SNMPv2-SMI;
	
	
		-- 1.3.6.1.4.1.589.1
		netCtrlDevMIB MODULE-IDENTITY 
			LAST-UPDATED "201701181406Z"		-- January 18, 2017 at 14:06 GMT
			ORGANIZATION 
				"Organization."
			CONTACT-INFO 
				"Contact-info."
			DESCRIPTION 
				"Description."
			::= { lctx 1 }

		
	
--
-- Node definitions
--
	
		-- 1.3.6.1.4.1.589
		lctx OBJECT IDENTIFIER ::= { enterprises 589 }

		
		-- 1.3.6.1.4.1.589.1.1
		paoFZLink OBJECT IDENTIFIER ::= { netCtrlDevMIB 1 }

		
		-- 1.3.6.1.4.1.589.1.2
		zhanSNet OBJECT IDENTIFIER ::= { netCtrlDevMIB 2 }

		
		-- 1.3.6.1.4.1.589.1.2.1
		zwSysCfg OBJECT IDENTIFIER ::= { zhanSNet 1 }

		
		-- 1.3.6.1.4.1.589.1.2.1.1
		mode OBJECT-TYPE
			SYNTAX Integer32
			MAX-ACCESS read-write
			STATUS current
			DESCRIPTION
				"Description."
			::= { zwSysCfg 1 }

		
		-- 1.3.6.1.4.1.589.1.2.1.2
		devSeq OBJECT-TYPE
			SYNTAX OCTET STRING
			MAX-ACCESS read-write
			STATUS current
			DESCRIPTION
				"Description."
			::= { zwSysCfg 2 }

		
		-- 1.3.6.1.4.1.589.1.2.1.3
		armyNum OBJECT-TYPE
			SYNTAX OCTET STRING
			MAX-ACCESS read-write
			STATUS current
			DESCRIPTION
				"Description."
			::= { zwSysCfg 3 }

		
		-- 1.3.6.1.4.1.589.1.2.1.4
		phoneLen OBJECT-TYPE
			SYNTAX Integer32
			MAX-ACCESS read-write
			STATUS current
			DESCRIPTION
				"Description."
			::= { zwSysCfg 4 }

		
		-- 1.3.6.1.4.1.589.1.2.1.5
		audioCodec OBJECT-TYPE
			SYNTAX Integer32
			MAX-ACCESS read-write
			STATUS current
			DESCRIPTION
				"Description."
			::= { zwSysCfg 5 }

		
		-- 1.3.6.1.4.1.589.1.2.1.6
		asNum OBJECT-TYPE
			SYNTAX OCTET STRING
			MAX-ACCESS read-write
			STATUS current
			DESCRIPTION
				"Description."
			::= { zwSysCfg 6 }

		
		-- 1.3.6.1.4.1.589.1.2.2
		zwUsrTable OBJECT-TYPE
			SYNTAX SEQUENCE OF ZwUsrEntry
			MAX-ACCESS not-accessible
			STATUS current
			DESCRIPTION
				"Description."
			::= { zhanSNet 2 }

		
		-- 1.3.6.1.4.1.589.1.2.2.1
		zwUsrEntry OBJECT-TYPE
			SYNTAX ZwUsrEntry
			MAX-ACCESS not-accessible
			STATUS current
			DESCRIPTION
				"Description."
			INDEX { usrNumber }
			::= { zwUsrTable 1 }

		
		ZwUsrEntry ::=
			SEQUENCE { 
				usrNumber
					OCTET STRING,
				secNum
					OCTET STRING
			 }

		-- 1.3.6.1.4.1.589.1.2.2.1.1
		usrNumber OBJECT-TYPE
			SYNTAX OCTET STRING
			MAX-ACCESS read-write
			STATUS current
			DESCRIPTION
				"Description."
			::= { zwUsrEntry 1 }

		
		-- 1.3.6.1.4.1.589.1.2.2.1.2
		secNum OBJECT-TYPE
			SYNTAX OCTET STRING
			MAX-ACCESS read-write
			STATUS current
			DESCRIPTION
				"Description."
			::= { zwUsrEntry 2 }

		
		-- 1.3.6.1.4.1.589.1.2.3
		zwConfTable OBJECT-TYPE
			SYNTAX SEQUENCE OF ZwConfEntry
			MAX-ACCESS not-accessible
			STATUS current
			DESCRIPTION
				"Description."
			::= { zhanSNet 3 }

		
		-- 1.3.6.1.4.1.589.1.2.3.1
		zwConfEntry OBJECT-TYPE
			SYNTAX ZwConfEntry
			MAX-ACCESS not-accessible
			STATUS current
			DESCRIPTION
				"Description."
			INDEX { zwConfNum }
			::= { zwConfTable 1 }

		
		ZwConfEntry ::=
			SEQUENCE { 
				zwConfNum
					OCTET STRING,
				zwPartCnt
					Integer32,
				zwPartNum0
					OCTET STRING,
				zwPartNum1
					OCTET STRING,
				zwPartNum2
					OCTET STRING,
				zwPartNum3
					OCTET STRING,
				zwPartNum4
					OCTET STRING,
				zwPartNum5
					OCTET STRING,
				zwPartNum6
					OCTET STRING,
				zwPartNum7
					OCTET STRING,
				zwPartNum8
					OCTET STRING,
				zwPartNum9
					OCTET STRING,
				zwPartNum10
					OCTET STRING,
				zwPartNum11
					OCTET STRING,
				zwPartNum12
					OCTET STRING,
				zwPartNum13
					OCTET STRING,
				zwPartNum14
					OCTET STRING,
				zwPartNum15
					OCTET STRING
			 }

		-- 1.3.6.1.4.1.589.1.2.3.1.1
		zwConfNum OBJECT-TYPE
			SYNTAX OCTET STRING
			MAX-ACCESS read-write
			STATUS current
			DESCRIPTION
				"Number of Conference"
			::= { zwConfEntry 1 }

		
		-- 1.3.6.1.4.1.589.1.2.3.1.2
		zwPartCnt OBJECT-TYPE
			SYNTAX Integer32
			MAX-ACCESS read-write
			STATUS current
			DESCRIPTION
				"part cnt in the conference"
			::= { zwConfEntry 2 }

		
		-- 1.3.6.1.4.1.589.1.2.3.1.3
		zwPartNum0 OBJECT-TYPE
			SYNTAX OCTET STRING
			MAX-ACCESS read-write
			STATUS current
			DESCRIPTION
				"part number"
			::= { zwConfEntry 3 }

		
		-- 1.3.6.1.4.1.589.1.2.3.1.4
		zwPartNum1 OBJECT-TYPE
			SYNTAX OCTET STRING
			MAX-ACCESS read-write
			STATUS current
			DESCRIPTION			" "
			::= { zwConfEntry 4 }

		
		-- 1.3.6.1.4.1.589.1.2.3.1.5
		zwPartNum2 OBJECT-TYPE
			SYNTAX OCTET STRING
			MAX-ACCESS read-write
			STATUS current
			DESCRIPTION			" "
			::= { zwConfEntry 5 }

		
		-- 1.3.6.1.4.1.589.1.2.3.1.6
		zwPartNum3 OBJECT-TYPE
			SYNTAX OCTET STRING
			MAX-ACCESS read-write
			STATUS current
			DESCRIPTION			" "
			::= { zwConfEntry 6 }

		
		-- 1.3.6.1.4.1.589.1.2.3.1.7
		zwPartNum4 OBJECT-TYPE
			SYNTAX OCTET STRING
			MAX-ACCESS read-write
			STATUS current
			DESCRIPTION			" "
			::= { zwConfEntry 7 }

		
		-- 1.3.6.1.4.1.589.1.2.3.1.9
		zwPartNum5 OBJECT-TYPE
			SYNTAX OCTET STRING
			MAX-ACCESS read-write
			STATUS current
			DESCRIPTION			" "
			::= { zwConfEntry 9 }

		
		-- 1.3.6.1.4.1.589.1.2.3.1.10
		zwPartNum6 OBJECT-TYPE
			SYNTAX OCTET STRING
			MAX-ACCESS read-write
			STATUS current
			DESCRIPTION			" "
			::= { zwConfEntry 10 }

		
		-- 1.3.6.1.4.1.589.1.2.3.1.11
		zwPartNum7 OBJECT-TYPE
			SYNTAX OCTET STRING
			MAX-ACCESS read-write
			STATUS current
			DESCRIPTION			" "
			::= { zwConfEntry 11 }

		
		-- 1.3.6.1.4.1.589.1.2.3.1.12
		zwPartNum8 OBJECT-TYPE
			SYNTAX OCTET STRING
			MAX-ACCESS read-write
			STATUS current
			DESCRIPTION			" "
			::= { zwConfEntry 12 }

		
		-- 1.3.6.1.4.1.589.1.2.3.1.13
		zwPartNum9 OBJECT-TYPE
			SYNTAX OCTET STRING
			MAX-ACCESS read-write
			STATUS current
			DESCRIPTION			" "
			::= { zwConfEntry 13 }

		
		-- 1.3.6.1.4.1.589.1.2.3.1.14
		zwPartNum10 OBJECT-TYPE
			SYNTAX OCTET STRING
			MAX-ACCESS read-write
			STATUS current
			DESCRIPTION
				"part number"
			::= { zwConfEntry 14 }

		
		-- 1.3.6.1.4.1.589.1.2.3.1.15
		zwPartNum11 OBJECT-TYPE
			SYNTAX OCTET STRING
			MAX-ACCESS read-write
			STATUS current
			DESCRIPTION
				"part number"
			::= { zwConfEntry 15 }

		
		-- 1.3.6.1.4.1.589.1.2.3.1.16
		zwPartNum12 OBJECT-TYPE
			SYNTAX OCTET STRING
			MAX-ACCESS read-write
			STATUS current
			DESCRIPTION
				"part number"
			::= { zwConfEntry 16 }

		
		-- 1.3.6.1.4.1.589.1.2.3.1.17
		zwPartNum13 OBJECT-TYPE
			SYNTAX OCTET STRING
			MAX-ACCESS read-write
			STATUS current
			DESCRIPTION
				"part number"
			::= { zwConfEntry 17 }

		
		-- 1.3.6.1.4.1.589.1.2.3.1.18
		zwPartNum14 OBJECT-TYPE
			SYNTAX OCTET STRING
			MAX-ACCESS read-write
			STATUS current
			DESCRIPTION
				"part number"
			::= { zwConfEntry 18 }

		
		-- 1.3.6.1.4.1.589.1.2.3.1.19
		zwPartNum15 OBJECT-TYPE
			SYNTAX OCTET STRING
			MAX-ACCESS read-write
			STATUS current
			DESCRIPTION
				"part number"
			::= { zwConfEntry 19 }

		
		-- 1.3.6.1.4.1.589.1.2.4
		zwZxTable OBJECT-TYPE
			SYNTAX SEQUENCE OF ZwZxEntry
			MAX-ACCESS not-accessible
			STATUS current
			DESCRIPTION
				"Description."
			::= { zhanSNet 4 }

		
		-- 1.3.6.1.4.1.589.1.2.4.1
		zwZxEntry OBJECT-TYPE
			SYNTAX ZwZxEntry
			MAX-ACCESS not-accessible
			STATUS current
			DESCRIPTION
				"Description."
			INDEX { port }
			::= { zwZxTable 1 }

		
		ZwZxEntry ::=
			SEQUENCE { 
				phoneID
					INTEGER,
				port
					Integer32,
				army
					OCTET STRING,
				calleeNum
					OCTET STRING,
				zxStatus
					Integer32
			 }

		-- 1.3.6.1.4.1.589.1.2.4.1.1
		phoneID OBJECT-TYPE
			SYNTAX INTEGER
			MAX-ACCESS read-write
			STATUS current
			DESCRIPTION
				"Description."
			::= { zwZxEntry 1 }

		
		-- 1.3.6.1.4.1.589.1.2.4.1.2
		port OBJECT-TYPE
			SYNTAX Integer32 (1..50)
			MAX-ACCESS read-write
			STATUS current
			DESCRIPTION
				"Description."
			::= { zwZxEntry 2 }

		
		-- 1.3.6.1.4.1.589.1.2.4.1.3
		army OBJECT-TYPE
			SYNTAX OCTET STRING
			MAX-ACCESS read-write
			STATUS current
			DESCRIPTION
				"Description."
			::= { zwZxEntry 3 }

		
		-- 1.3.6.1.4.1.589.1.2.4.1.4
		calleeNum OBJECT-TYPE
			SYNTAX OCTET STRING
			MAX-ACCESS read-write
			STATUS current
			DESCRIPTION
				"Description."
			::= { zwZxEntry 4 }

		
		-- 1.3.6.1.4.1.589.1.2.4.1.5
		zxStatus OBJECT-TYPE
			SYNTAX Integer32
			MAX-ACCESS read-write
			STATUS current
			DESCRIPTION
				"Description."
			::= { zwZxEntry 5 }

		
		-- 1.3.6.1.4.1.589.1.2.5
		qlPortTable OBJECT-TYPE
			SYNTAX SEQUENCE OF QlPortEntry
			MAX-ACCESS not-accessible
			STATUS current
			DESCRIPTION
				"Description."
			::= { zhanSNet 5 }

		
		-- 1.3.6.1.4.1.589.1.2.5.1
		qlPortEntry OBJECT-TYPE
			SYNTAX QlPortEntry
			MAX-ACCESS not-accessible
			STATUS current
			DESCRIPTION
				"Description."
			INDEX { portNum }
			::= { qlPortTable 1 }

		
		QlPortEntry ::=
			SEQUENCE { 
				portNum
					Integer32,
				portType
					Integer32,
				speed
					Integer32,
				dyMod
					Integer32,
				clickType
					Integer32,
				masterFlg
					Integer32,
				loopFlg
					Integer32
			 }

		-- 1.3.6.1.4.1.589.1.2.5.1.1
		portNum OBJECT-TYPE
			SYNTAX Integer32 (1..50)
			MAX-ACCESS read-write
			STATUS current
			DESCRIPTION
				"Description."
			::= { qlPortEntry 1 }

		
		-- 1.3.6.1.4.1.589.1.2.5.1.2
		portType OBJECT-TYPE
			SYNTAX Integer32
			MAX-ACCESS read-write
			STATUS current
			DESCRIPTION
				"Description."
			::= { qlPortEntry 2 }

		
		-- 1.3.6.1.4.1.589.1.2.5.1.3
		speed OBJECT-TYPE
			SYNTAX Integer32
			MAX-ACCESS read-write
			STATUS current
			DESCRIPTION
				"Description."
			::= { qlPortEntry 3 }

		
		-- 1.3.6.1.4.1.589.1.2.5.1.4
		dyMod OBJECT-TYPE
			SYNTAX Integer32
			MAX-ACCESS read-write
			STATUS current
			DESCRIPTION
				"Description."
			::= { qlPortEntry 4 }

		
		-- 1.3.6.1.4.1.589.1.2.5.1.5
		clickType OBJECT-TYPE
			SYNTAX Integer32
			MAX-ACCESS read-write
			STATUS current
			DESCRIPTION
				"Description."
			::= { qlPortEntry 5 }

		
		-- 1.3.6.1.4.1.589.1.2.5.1.6
		masterFlg OBJECT-TYPE
			SYNTAX Integer32
			MAX-ACCESS read-write
			STATUS current
			DESCRIPTION
				"Description."
			::= { qlPortEntry 6 }

		
		-- 1.3.6.1.4.1.589.1.2.5.1.7
		loopFlg OBJECT-TYPE
			SYNTAX Integer32
			MAX-ACCESS read-write
			STATUS current
			DESCRIPTION
				"Description."
			::= { qlPortEntry 7 }

		
		-- 1.3.6.1.4.1.589.1.2.6
		radioPortTable OBJECT-TYPE
			SYNTAX SEQUENCE OF RadioPortEntry
			MAX-ACCESS not-accessible
			STATUS current
			DESCRIPTION
				"Description."
			::= { zhanSNet 6 }

		
		-- 1.3.6.1.4.1.589.1.2.6.1
		radioPortEntry OBJECT-TYPE
			SYNTAX RadioPortEntry
			MAX-ACCESS not-accessible
			STATUS current
			DESCRIPTION
				"Description."
			INDEX { radioPortNum }
			::= { radioPortTable 1 }

		
		RadioPortEntry ::=
			SEQUENCE { 
				radioPortNum
					Integer32,
				radioPortType
					Integer32,
				radioPortWorkMod
					Integer32
			 }

		-- 1.3.6.1.4.1.589.1.2.6.1.1
		radioPortNum OBJECT-TYPE
			SYNTAX Integer32 (1..50)
			MAX-ACCESS read-write
			STATUS current
			DESCRIPTION
				"Description."
			::= { radioPortEntry 1 }

		
		-- 1.3.6.1.4.1.589.1.2.6.1.2
		radioPortType OBJECT-TYPE
			SYNTAX Integer32
			MAX-ACCESS read-write
			STATUS current
			DESCRIPTION
				"Description."
			::= { radioPortEntry 2 }

		
		-- 1.3.6.1.4.1.589.1.2.6.1.3
		radioPortWorkMod OBJECT-TYPE
			SYNTAX Integer32
			MAX-ACCESS read-write
			STATUS current
			DESCRIPTION
				"Description."
			::= { radioPortEntry 3 }

		
		-- 1.3.6.1.4.1.589.1.2.7
		ipPortTable OBJECT-TYPE
			SYNTAX SEQUENCE OF IpPortEntry
			MAX-ACCESS not-accessible
			STATUS current
			DESCRIPTION
				"Description."
			::= { zhanSNet 7 }

		
		-- 1.3.6.1.4.1.589.1.2.7.1
		ipPortEntry OBJECT-TYPE
			SYNTAX IpPortEntry
			MAX-ACCESS not-accessible
			STATUS current
			DESCRIPTION
				"Description."
			INDEX { ipPortNum }
			::= { ipPortTable 1 }

		
		IpPortEntry ::=
			SEQUENCE { 
				ipPortNum
					Integer32,
				ipPortType
					Integer32,
				addrType
					Integer32,
				ipaddr
					OCTET STRING,
				mask
					Integer32,
				routeP
					Integer32,
				groupFlg
					Integer32,
				mplsFlg
					Integer32,
				linkP
					Integer32,
				mtu
					Integer32
			 }

		-- 1.3.6.1.4.1.589.1.2.7.1.1
		ipPortNum OBJECT-TYPE
			SYNTAX Integer32 (1..50)
			MAX-ACCESS read-write
			STATUS current
			DESCRIPTION
				"Description."
			::= { ipPortEntry 1 }

		
		-- 1.3.6.1.4.1.589.1.2.7.1.2
		ipPortType OBJECT-TYPE
			SYNTAX Integer32
			MAX-ACCESS read-write
			STATUS current
			DESCRIPTION
				"Description."
			::= { ipPortEntry 2 }

		
		-- 1.3.6.1.4.1.589.1.2.7.1.3
		addrType OBJECT-TYPE
			SYNTAX Integer32
			MAX-ACCESS read-write
			STATUS current
			DESCRIPTION
				"Description."
			::= { ipPortEntry 3 }

		
		-- 1.3.6.1.4.1.589.1.2.7.1.4
		ipaddr OBJECT-TYPE
			SYNTAX OCTET STRING
			MAX-ACCESS read-write
			STATUS current
			DESCRIPTION
				"Description."
			::= { ipPortEntry 4 }

		
		-- 1.3.6.1.4.1.589.1.2.7.1.5
		mask OBJECT-TYPE
			SYNTAX Integer32
			MAX-ACCESS read-write
			STATUS current
			DESCRIPTION
				"Description."
			::= { ipPortEntry 5 }

		
		-- 1.3.6.1.4.1.589.1.2.7.1.6
		routeP OBJECT-TYPE
			SYNTAX Integer32
			MAX-ACCESS read-write
			STATUS current
			DESCRIPTION
				"Description."
			::= { ipPortEntry 6 }

		
		-- 1.3.6.1.4.1.589.1.2.7.1.7
		groupFlg OBJECT-TYPE
			SYNTAX Integer32
			MAX-ACCESS read-write
			STATUS current
			DESCRIPTION
				"Description."
			::= { ipPortEntry 7 }

		
		-- 1.3.6.1.4.1.589.1.2.7.1.8
		mplsFlg OBJECT-TYPE
			SYNTAX Integer32
			MAX-ACCESS read-write
			STATUS current
			DESCRIPTION
				"Description."
			::= { ipPortEntry 8 }

		
		-- 1.3.6.1.4.1.589.1.2.7.1.9
		linkP OBJECT-TYPE
			SYNTAX Integer32
			MAX-ACCESS read-write
			STATUS current
			DESCRIPTION
				"Description."
			::= { ipPortEntry 9 }

		
		-- 1.3.6.1.4.1.589.1.2.7.1.10
		mtu OBJECT-TYPE
			SYNTAX Integer32
			MAX-ACCESS read-write
			STATUS current
			DESCRIPTION
				"Description."
			::= { ipPortEntry 10 }

		
		-- 1.3.6.1.4.1.589.1.2.8
		frpCfgTable OBJECT-TYPE
			SYNTAX SEQUENCE OF FrpCfgEntry
			MAX-ACCESS not-accessible
			STATUS current
			DESCRIPTION
				"Description."
			::= { zhanSNet 8 }

		
		-- 1.3.6.1.4.1.589.1.2.8.1
		frpCfgEntry OBJECT-TYPE
			SYNTAX FrpCfgEntry
			MAX-ACCESS not-accessible
			STATUS current
			DESCRIPTION
				"Description."
			INDEX { frpPortNum }
			::= { frpCfgTable 1 }

		
		FrpCfgEntry ::=
			SEQUENCE { 
				frpPortNum
					Integer32,
				frpAsID
					OBJECT IDENTIFIER,
				frpHello
					Integer32,
				frpHold
					Integer32
			 }

		-- 1.3.6.1.4.1.589.1.2.8.1.1
		frpPortNum OBJECT-TYPE
			SYNTAX Integer32 (1..50)
			MAX-ACCESS read-write
			STATUS current
			DESCRIPTION
				"Description."
			::= { frpCfgEntry 1 }

		
		-- 1.3.6.1.4.1.589.1.2.8.1.2
		frpAsID OBJECT-TYPE
			SYNTAX OBJECT IDENTIFIER
			MAX-ACCESS read-write
			STATUS current
			DESCRIPTION
				"Description."
			::= { frpCfgEntry 2 }

		
		-- 1.3.6.1.4.1.589.1.2.8.1.3
		frpHello OBJECT-TYPE
			SYNTAX Integer32
			MAX-ACCESS read-write
			STATUS current
			DESCRIPTION
				"Description."
			::= { frpCfgEntry 3 }

		
		-- 1.3.6.1.4.1.589.1.2.8.1.4
		frpHold OBJECT-TYPE
			SYNTAX Integer32
			MAX-ACCESS read-write
			STATUS current
			DESCRIPTION
				"Description."
			::= { frpCfgEntry 4 }

		
		-- 1.3.6.1.4.1.589.1.2.9
		routeCffTable OBJECT-TYPE
			SYNTAX SEQUENCE OF RouteCffEntry
			MAX-ACCESS not-accessible
			STATUS current
			DESCRIPTION
				"Description."
			::= { zhanSNet 9 }

		
		-- 1.3.6.1.4.1.589.1.2.9.1
		routeCffEntry OBJECT-TYPE
			SYNTAX RouteCffEntry
			MAX-ACCESS not-accessible
			STATUS current
			DESCRIPTION
				"Description."
			INDEX { proto }
			::= { routeCffTable 1 }

		
		RouteCffEntry ::=
			SEQUENCE { 
				proto
					Integer32,
				enStaticRT
					Integer32,
				enDLRt
					Integer32,
				enFRP
					Integer32,
				enOSPF
					Integer32,
				enRIP
					Integer32,
				enTIRP
					Integer32,
				frpAs
					OCTET STRING
			 }

		-- 1.3.6.1.4.1.589.1.2.9.1.1
		proto OBJECT-TYPE
			SYNTAX Integer32 (1..4)
			MAX-ACCESS read-write
			STATUS current
			DESCRIPTION
				"Description."
			::= { routeCffEntry 1 }

		
		-- 1.3.6.1.4.1.589.1.2.9.1.2
		enStaticRT OBJECT-TYPE
			SYNTAX Integer32
			MAX-ACCESS read-write
			STATUS current
			DESCRIPTION
				"Description."
			::= { routeCffEntry 2 }

		
		-- 1.3.6.1.4.1.589.1.2.9.1.3
		enDLRt OBJECT-TYPE
			SYNTAX Integer32
			MAX-ACCESS read-write
			STATUS current
			DESCRIPTION
				"Description."
			::= { routeCffEntry 3 }

		
		-- 1.3.6.1.4.1.589.1.2.9.1.4
		enFRP OBJECT-TYPE
			SYNTAX Integer32
			MAX-ACCESS read-write
			STATUS current
			DESCRIPTION
				"Description."
			::= { routeCffEntry 4 }

		
		-- 1.3.6.1.4.1.589.1.2.9.1.5
		enOSPF OBJECT-TYPE
			SYNTAX Integer32
			MAX-ACCESS read-write
			STATUS current
			DESCRIPTION
				"Description."
			::= { routeCffEntry 5 }

		
		-- 1.3.6.1.4.1.589.1.2.9.1.6
		enRIP OBJECT-TYPE
			SYNTAX Integer32
			MAX-ACCESS read-write
			STATUS current
			DESCRIPTION
				"Description."
			::= { routeCffEntry 6 }

		
		-- 1.3.6.1.4.1.589.1.2.9.1.7
		enTIRP OBJECT-TYPE
			SYNTAX Integer32
			MAX-ACCESS read-write
			STATUS current
			DESCRIPTION
				"Description."
			::= { routeCffEntry 7 }

		
		-- 1.3.6.1.4.1.589.1.2.9.1.8
		frpAs OBJECT-TYPE
			SYNTAX OCTET STRING
			MAX-ACCESS read-write
			STATUS current
			DESCRIPTION
				"Description."
			::= { routeCffEntry 8 }

		
		-- 1.3.6.1.4.1.589.1.2.10
		routeJHTable OBJECT-TYPE
			SYNTAX SEQUENCE OF RouteJHEntry
			MAX-ACCESS not-accessible
			STATUS current
			DESCRIPTION
				"Description."
			::= { zhanSNet 10 }

		
		-- 1.3.6.1.4.1.589.1.2.10.1
		routeJHEntry OBJECT-TYPE
			SYNTAX RouteJHEntry
			MAX-ACCESS not-accessible
			STATUS current
			DESCRIPTION
				"Description."
			INDEX { lyjhPortNum }
			::= { routeJHTable 1 }

		
		RouteJHEntry ::=
			SEQUENCE { 
				lyjhPortNum
					Integer32,
				lyjhIP
					OCTET STRING,
				lyjhMask
					Integer32,
				lyjhRouteP
					Integer32,
				lyjhEnFlg
					Integer32
			 }

		-- 1.3.6.1.4.1.589.1.2.10.1.1
		lyjhPortNum OBJECT-TYPE
			SYNTAX Integer32 (1..50)
			MAX-ACCESS read-write
			STATUS current
			DESCRIPTION
				"Description."
			::= { routeJHEntry 1 }

		
		-- 1.3.6.1.4.1.589.1.2.10.1.2
		lyjhIP OBJECT-TYPE
			SYNTAX OCTET STRING
			MAX-ACCESS read-write
			STATUS current
			DESCRIPTION
				"Description."
			::= { routeJHEntry 2 }

		
		-- 1.3.6.1.4.1.589.1.2.10.1.3
		lyjhMask OBJECT-TYPE
			SYNTAX Integer32
			MAX-ACCESS read-write
			STATUS current
			DESCRIPTION
				"Description."
			::= { routeJHEntry 3 }

		
		-- 1.3.6.1.4.1.589.1.2.10.1.4
		lyjhRouteP OBJECT-TYPE
			SYNTAX Integer32
			MAX-ACCESS read-write
			STATUS current
			DESCRIPTION
				"Description."
			::= { routeJHEntry 4 }

		
		-- 1.3.6.1.4.1.589.1.2.10.1.5
		lyjhEnFlg OBJECT-TYPE
			SYNTAX Integer32
			MAX-ACCESS read-write
			STATUS current
			DESCRIPTION
				"Description."
			::= { routeJHEntry 5 }

		
		-- 1.3.6.1.4.1.589.1.2.11
		stRouteTable OBJECT-TYPE
			SYNTAX SEQUENCE OF StRouteEntry
			MAX-ACCESS not-accessible
			STATUS current
			DESCRIPTION
				"Description."
			::= { zhanSNet 11 }

		
		-- 1.3.6.1.4.1.589.1.2.11.1
		stRouteEntry OBJECT-TYPE
			SYNTAX StRouteEntry
			MAX-ACCESS not-accessible
			STATUS current
			DESCRIPTION
				"Description."
			INDEX { dstIP }
			::= { stRouteTable 1 }

		
		StRouteEntry ::=
			SEQUENCE { 
				dstIP
					OCTET STRING,
				dstMask
					Integer32,
				gwAddr
					OCTET STRING
			 }

		-- 1.3.6.1.4.1.589.1.2.11.1.2
		dstIP OBJECT-TYPE
			SYNTAX OCTET STRING
			MAX-ACCESS read-write
			STATUS current
			DESCRIPTION
				"Description."
			::= { stRouteEntry 2 }

		
		-- 1.3.6.1.4.1.589.1.2.11.1.3
		dstMask OBJECT-TYPE
			SYNTAX Integer32
			MAX-ACCESS read-write
			STATUS current
			DESCRIPTION
				"Description."
			::= { stRouteEntry 3 }

		
		-- 1.3.6.1.4.1.589.1.2.11.1.5
		gwAddr OBJECT-TYPE
			SYNTAX OCTET STRING
			MAX-ACCESS read-write
			STATUS current
			DESCRIPTION
				"Description."
			::= { stRouteEntry 5 }

		
		-- 1.3.6.1.4.1.589.1.3
		mediaGW OBJECT IDENTIFIER ::= { netCtrlDevMIB 3 }

		
-- 1,zhuangjiaMode; 
-- 2,paoFangMode; 
-- 5,xiWeiKuoZhanMode
		-- 1.3.6.1.4.1.589.1.3.1
		workMode OBJECT-TYPE
			SYNTAX INTEGER
				{
				zhuanJiaMod(1),
				paoFMod(2),
				seatExtMod(5)
				}
			MAX-ACCESS read-write
			STATUS current
			DESCRIPTION
				"defined work mode"
			::= { mediaGW 1 }

		
-- 席位扩展模式下，中继呼入振入分机配置
		-- 1.3.6.1.4.1.589.1.3.2
		zhenRFenjTable OBJECT-TYPE
			SYNTAX SEQUENCE OF ZhenRFenjEntry
			MAX-ACCESS not-accessible
			STATUS current
			DESCRIPTION
				"config table of ZhenRu Fenji"
			::= { mediaGW 2 }

		
		-- 1.3.6.1.4.1.589.1.3.2.1
		zhenRFenjEntry OBJECT-TYPE
			SYNTAX ZhenRFenjEntry
			MAX-ACCESS not-accessible
			STATUS current
			DESCRIPTION
				"parameters of ZhenRu Fenji"
			INDEX { zjID }
			::= { zhenRFenjTable 1 }

		
		ZhenRFenjEntry ::=
			SEQUENCE { 
				zjID
					Integer32,
				fenJID
					Integer32,
				fenJNum
					OCTET STRING
			 }

		-- 1.3.6.1.4.1.589.1.3.2.1.2
		zjID OBJECT-TYPE
			SYNTAX Integer32 (1..128)
			MAX-ACCESS read-write
			STATUS current
			DESCRIPTION
				"chan Id of Repeater"
			::= { zhenRFenjEntry 2 }

		
		-- 1.3.6.1.4.1.589.1.3.2.1.3
		fenJID OBJECT-TYPE
			SYNTAX Integer32
			MAX-ACCESS read-write
			STATUS current
			DESCRIPTION
				"chanID of FenJi"
			::= { zhenRFenjEntry 3 }

		
		-- 1.3.6.1.4.1.589.1.3.2.1.4
		fenJNum OBJECT-TYPE
			SYNTAX OCTET STRING
			MAX-ACCESS read-write
			STATUS current
			DESCRIPTION
				"phone Num of FenJi"
			::= { zhenRFenjEntry 4 }

		
		-- 1.3.6.1.4.1.589.1.3.3
		conferenceTable OBJECT-TYPE
			SYNTAX SEQUENCE OF ConferenceEntry
			MAX-ACCESS not-accessible
			STATUS current
			DESCRIPTION
				"Description."
			::= { mediaGW 3 }

		
		-- 1.3.6.1.4.1.589.1.3.3.1
		conferenceEntry OBJECT-TYPE
			SYNTAX ConferenceEntry
			MAX-ACCESS not-accessible
			STATUS current
			DESCRIPTION
				"Description."
			INDEX { confNum }
			::= { conferenceTable 1 }

		
		ConferenceEntry ::=
			SEQUENCE { 
				confNum
					OCTET STRING,
				partCnt
					Integer32,
				partNum0
					OCTET STRING,
				partNum1
					OCTET STRING,
				partNum2
					OCTET STRING,
				partNum3
					OCTET STRING,
				partNum4
					OCTET STRING,
				partNum5
					OCTET STRING
			 }

		-- 1.3.6.1.4.1.589.1.3.3.1.1
		confNum OBJECT-TYPE
			SYNTAX OCTET STRING
			MAX-ACCESS read-write
			STATUS current
			DESCRIPTION
				"Number of Conference"
			::= { conferenceEntry 1 }

		
		-- 1.3.6.1.4.1.589.1.3.3.1.2
		partCnt OBJECT-TYPE
			SYNTAX Integer32
			MAX-ACCESS read-write
			STATUS current
			DESCRIPTION
				"part cnt in the conference"
			::= { conferenceEntry 2 }

		
		-- 1.3.6.1.4.1.589.1.3.3.1.3
		partNum0 OBJECT-TYPE
			SYNTAX OCTET STRING
			MAX-ACCESS read-write
			STATUS current
			DESCRIPTION
				"part number"
			::= { conferenceEntry 3 }

		
		-- 1.3.6.1.4.1.589.1.3.3.1.4
		partNum1 OBJECT-TYPE
			SYNTAX OCTET STRING
			MAX-ACCESS read-write
			STATUS current
			DESCRIPTION			" "
			::= { conferenceEntry 4 }

		
		-- 1.3.6.1.4.1.589.1.3.3.1.5
		partNum2 OBJECT-TYPE
			SYNTAX OCTET STRING
			MAX-ACCESS read-write
			STATUS current
			DESCRIPTION			" "
			::= { conferenceEntry 5 }

		
		-- 1.3.6.1.4.1.589.1.3.3.1.6
		partNum3 OBJECT-TYPE
			SYNTAX OCTET STRING
			MAX-ACCESS read-write
			STATUS current
			DESCRIPTION			" "
			::= { conferenceEntry 6 }

		
		-- 1.3.6.1.4.1.589.1.3.3.1.7
		partNum4 OBJECT-TYPE
			SYNTAX OCTET STRING
			MAX-ACCESS read-write
			STATUS current
			DESCRIPTION			" "
			::= { conferenceEntry 7 }

		
		-- 1.3.6.1.4.1.589.1.3.3.1.8
		partNum5 OBJECT-TYPE
			SYNTAX OCTET STRING
			MAX-ACCESS read-write
			STATUS current
			DESCRIPTION			" "
			::= { conferenceEntry 8 }

		
		-- 1.3.6.1.4.1.589.1.3.4
		gPortMode OBJECT-TYPE
			SYNTAX Integer32 (0..3)
			MAX-ACCESS read-write
			STATUS current
			DESCRIPTION
				"Description."
			DEFVAL { '0'b }
			::= { mediaGW 4 }
-- 0,xwkz 2M
-- 1,xwkz 1M
-- 2,xwkz 192K
-- 3,duLiKaiSheShi
		
	
	END

--
-- LCTX-NET-CTRL-DEV.mib
--
