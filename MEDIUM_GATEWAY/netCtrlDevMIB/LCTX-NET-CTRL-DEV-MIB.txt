--
-- LCTX-NET-CTRL-DEV.mib
-- MIB generated by MG-SOFT Visual MIB Builder Version 6.0  Build 88
-- Thursday, February 16, 2017 at 21:11:56
--

	LCTX-NET-CTRL-DEV DEFINITIONS ::= BEGIN
 
		IMPORTS
			enterprises, Integer32, OBJECT-TYPE, MODULE-IDENTITY			
				FROM SNMPv2-SMI;
	
	
		-- 1.3.6.1.4.1.589.1
		netCtrlDevMIB MODULE-IDENTITY 
			LAST-UPDATED "201701181406Z"		-- January 18, 2017 at 14:06 GMT
			ORGANIZATION 
				"Organization."
			CONTACT-INFO 
				"Contact-info."
			DESCRIPTION 
				"Description."
			::= { lctx 1 }

		
	
--
-- Node definitions
--
	
		-- 1.3.6.1.4.1.589
		lctx OBJECT IDENTIFIER ::= { enterprises 589 }

		
		-- 1.3.6.1.4.1.589.1.1
		paoFZLink OBJECT IDENTIFIER ::= { netCtrlDevMIB 1 }

		
		-- 1.3.6.1.4.1.589.1.2
		zhanSNetwork OBJECT IDENTIFIER ::= { netCtrlDevMIB 2 }

		
		-- 1.3.6.1.4.1.589.1.3
		mediaGW OBJECT IDENTIFIER ::= { netCtrlDevMIB 3 }

		
-- 1,zhuangjiaMode; 
-- 2,paoFangMode; 
-- 5,xiWeiKuoZhanMode
		-- 1.3.6.1.4.1.589.1.3.1
		workMode OBJECT-TYPE
			SYNTAX INTEGER
				{
				zhuanJiaMod(1),
				paoFMod(2),
				seatExtMod(5)
				}
			MAX-ACCESS read-write
			STATUS current
			DESCRIPTION
				"defined work mode"
			::= { mediaGW 1 }

		
-- 席位扩展模式下，中继呼入振入分机配置
		-- 1.3.6.1.4.1.589.1.3.2
		zhenRFenjTable OBJECT-TYPE
			SYNTAX SEQUENCE OF ZhenRFenjEntry
			MAX-ACCESS not-accessible
			STATUS current
			DESCRIPTION
				"config table of ZhenRu Fenji"
			::= { mediaGW 2 }

		
		-- 1.3.6.1.4.1.589.1.3.2.1
		zhenRFenjEntry OBJECT-TYPE
			SYNTAX ZhenRFenjEntry
			MAX-ACCESS not-accessible
			STATUS current
			DESCRIPTION
				"parameters of ZhenRu Fenji"
			INDEX { zjID }
			::= { zhenRFenjTable 1 }

		
		ZhenRFenjEntry ::=
			SEQUENCE { 
				zjID
					Integer32,
				fenJID
					Integer32,
				fenJNum
					OCTET STRING
			 }

		-- 1.3.6.1.4.1.589.1.3.2.1.2
		zjID OBJECT-TYPE
			SYNTAX Integer32 (1..128)
			MAX-ACCESS read-write
			STATUS current
			DESCRIPTION
				"chan Id of Repeater"
			::= { zhenRFenjEntry 2 }

		
		-- 1.3.6.1.4.1.589.1.3.2.1.3
		fenJID OBJECT-TYPE
			SYNTAX Integer32
			MAX-ACCESS read-write
			STATUS current
			DESCRIPTION
				"chanID of FenJi"
			::= { zhenRFenjEntry 3 }

		
		-- 1.3.6.1.4.1.589.1.3.2.1.4
		fenJNum OBJECT-TYPE
			SYNTAX OCTET STRING
			MAX-ACCESS read-write
			STATUS current
			DESCRIPTION
				"phone Num of FenJi"
			::= { zhenRFenjEntry 4 }

		
		-- 1.3.6.1.4.1.589.1.3.3
		conferenceTable OBJECT-TYPE
			SYNTAX SEQUENCE OF ConferenceEntry
			MAX-ACCESS not-accessible
			STATUS current
			DESCRIPTION
				"Description."
			::= { mediaGW 3 }

		
		-- 1.3.6.1.4.1.589.1.3.3.1
		conferenceEntry OBJECT-TYPE
			SYNTAX ConferenceEntry
			MAX-ACCESS not-accessible
			STATUS current
			DESCRIPTION
				"Description."
			INDEX { confNum }
			::= { conferenceTable 1 }

		
		ConferenceEntry ::=
			SEQUENCE { 
				confNum
					OCTET STRING,
				partCnt
					Integer32,
				partNum0
					OCTET STRING,
				partNum1
					OCTET STRING,
				partNum2
					OCTET STRING,
				partNum3
					OCTET STRING,
				partNum4
					OCTET STRING,
				partNum5
					OCTET STRING
			 }

		-- 1.3.6.1.4.1.589.1.3.3.1.1
		confNum OBJECT-TYPE
			SYNTAX OCTET STRING
			MAX-ACCESS read-write
			STATUS current
			DESCRIPTION
				"Number of Conference"
			::= { conferenceEntry 1 }

		
		-- 1.3.6.1.4.1.589.1.3.3.1.2
		partCnt OBJECT-TYPE
			SYNTAX Integer32
			MAX-ACCESS read-write
			STATUS current
			DESCRIPTION
				"part cnt in the conference"
			::= { conferenceEntry 2 }

		
		-- 1.3.6.1.4.1.589.1.3.3.1.3
		partNum0 OBJECT-TYPE
			SYNTAX OCTET STRING
			MAX-ACCESS read-write
			STATUS current
			DESCRIPTION
				"part number"
			::= { conferenceEntry 3 }

		
		-- 1.3.6.1.4.1.589.1.3.3.1.4
		partNum1 OBJECT-TYPE
			SYNTAX OCTET STRING
			MAX-ACCESS read-write
			STATUS current
			DESCRIPTION			" "
			::= { conferenceEntry 4 }

		
		-- 1.3.6.1.4.1.589.1.3.3.1.5
		partNum2 OBJECT-TYPE
			SYNTAX OCTET STRING
			MAX-ACCESS read-write
			STATUS current
			DESCRIPTION			" "
			::= { conferenceEntry 5 }

		
		-- 1.3.6.1.4.1.589.1.3.3.1.6
		partNum3 OBJECT-TYPE
			SYNTAX OCTET STRING
			MAX-ACCESS read-write
			STATUS current
			DESCRIPTION			" "
			::= { conferenceEntry 6 }

		
		-- 1.3.6.1.4.1.589.1.3.3.1.7
		partNum4 OBJECT-TYPE
			SYNTAX OCTET STRING
			MAX-ACCESS read-write
			STATUS current
			DESCRIPTION			" "
			::= { conferenceEntry 7 }

		
		-- 1.3.6.1.4.1.589.1.3.3.1.8
		partNum5 OBJECT-TYPE
			SYNTAX OCTET STRING
			MAX-ACCESS read-write
			STATUS current
			DESCRIPTION			" "
			::= { conferenceEntry 8 }

		
		-- 1.3.6.1.4.1.589.1.3.4
		gPortMode OBJECT-TYPE
			SYNTAX Integer32 (0..3)
			MAX-ACCESS read-write
			STATUS current
			DESCRIPTION
				"Description."
			DEFVAL { '0'b }
			::= { mediaGW 4 }
-- 0,xwkz 2M
-- 1,xwkz 1M
-- 2,xwkz 192K
-- 3,duLiKaiSheShi
		
	
	END

--
-- LCTX-NET-CTRL-DEV.mib
--
